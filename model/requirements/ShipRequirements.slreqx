# ShipRequirements

## NEED-01: Platform Support (Functional)
Shipboard services and resources must support vessel operations.
- Rationale: The operator and crew need the means to conduct vessel operations so the vessel can serve the mission the owner assigned during pre-commissioning.

### REQ-101: Electrical Power (Functional)
The shipboard electrical plant shall supply power to loads in accordance with demand.
- Rationale: Electrical power is required to operate propulsion systems, auxiliary systems, and mission-specific systems.

#### REQ-102: Electrical Power Generation (Functional)
Generator sets shall be configured to produce the electrical power demanded by the shipboard load schedule for each defined operating condition.
- Rationale: Shipboard electrical loads require an onboard source of electrical power when shore-supplied power is unavailable.

#### REQ-103: Electrical Energy Distribution (Functional)
The electrical energy distribution network shall carry electrical energy from sources to loads as designated in the shipboard load schedule.
- Rationale: Generated, stored, or shore-supplied electrical energy must be transferred to the systems and equipment as demanded.

##### REQ-104: Shore Power (Functional)
Shore power interfaces shall accept shore-supplied electrical energy for distribution to designated shipboard loads.
- Rationale: Shore-supplied electricity allows designated vessel services to operate without relying solely on onboard electrical generation while the vessel is connected to shore facilities.

#### REQ-105: Load Power Continuity (Functional)
Uninterruptible Power Supplies, Emergency Generators, and Power Management Systems shall maintain the electrical power supplied to critical and essential loads during each defined loss-of-power condition.
- Rationale: Loss of electrical power to loads can prevent the vessel from maintaining safety-critical and mission-critical functions.

#### REQ-106: Electrical Power Quality (Functional)
Local automatic voltage regulator, governor, converter, and harmonic filter devices shall be used in tandem with central power management and transformer systems to regulate voltage, frequency, and waveform in accordance with the defined parameters.
- Rationale: Shipboard equipment requires electrical power within defined operating limits to function correctly and avoid damage or loss of performance.

#### REQ-107: BESS (Functional)
The BESS shall manage stored electrical energy in tandem with the electrical energy distribution network through their shared interfaces according to the shipboard load schedule.
- Rationale: Stored electrical energy supports designated shipboard loads under defined operating conditions when immediate power from another source is unavailable or insufficient.

### REQ-108: Machinery Fluid Services (Container)

#### REQ-109: Primary Cooling Service (Functional)
Primary coolants shall absorb and transport thermal energy from machinery by flowing through pressure- and temperature-controlled pipeline circuits networked around and through the machinery.
- Rationale: Both yard-built machinery and furnished machinery generate thermal energy during operation that must be transferred to an appropriate heat sink to maintain reliable operation and prevent thermal degradation.

#### REQ-110: Lubrication Service (Functional)
Lubrication oil shall service furnished machinery by flowing through pressure- and temperature-controlled pipeline networks and passing through machinery interfaces.
- Rationale: Furnished machinery accepts lubrication oil from the shipboard distribution system into its internal lubrication systems to mitigate friction caused by the relative motion between contacting mechanical surfaces.

#### REQ-111: Fuel Oil Supply (Functional)
Fuel oil shall flow through pressure- and temperature-controlled pipeline networks and pass through the interfaces of furnished fuel consumers.
- Rationale: Fuel consumers accept fuel oil from shipboard distribution systems into their internal combustion systems to convert chemical energy into the mechanical energy required for mechanical and electrical power generation.

#### REQ-112: Hydraulic Fluid Service (Functional)
Hydraulic fluid shall service furnished machinery by flowing through pressure- and temperature-controlled pipeline networks and passing through machinery interfaces.
The hydraulic fluid service shall pressurize and circulate hydraulic fluid to transmit power to installed hydraulically actuated machinery.
- Rationale: Furnished machinery accepts hydraulic fluid from the shipboard distribution system into its internal hydraulic system to transmit power and produce controlled mechanical motion or force.

#### REQ-113: Compressed Air Service (Functional)
Compressed air shall service furnished machinery by flowing through delivery networks and passing through machinery interfaces.
- Rationale: Furnished machinery accepts compressed air from the shipboard distribution system into its internal pneumatic system to convert the air's potential energy into pneumatic power.

### REQ-114: Thermal Management (Informational)
Yard-built systems shall allow operators to control the thermal conditions of media passing through, around, or consumed by shipboard equipment via the configuration of both OEM and aftermarket devices within media distribution networks.
passing through, around, out of, or consumed by (????)
- Rationale: Shipboard equipment generates thermal energy that must be managed to prevent overheating, preserve required equipment performance, and maintain acceptable machinery-space conditions; when feasible, thermal energy is recovered and reused to cut operational costs.

#### REQ-115: Secondary Cooling Service (Functional)
Secondary coolants shall absorb and transport thermal energy from primary coolants by flowing past the primary coolant over a shared boundary with the primary cooling loop.
flowing past shared boundary with primary cooling loop
Cooling fluids shall absorb and transport thermal energy from machinery by flowing through pressure- and temperature-controlled pipeline circuits networked around and through the machinery.
("distribution network")
- Rationale: To prevent heat accumulation beyond operating tolerances, heat that cannot be recovered must be rejected to a heat sink through pathways that maintain the isolation of primary and secondary coolants.

#### REQ-116: Waste Heat Recovery (Functional)
Fluids possessing waste heat shall flow into thermal energy transfer devices or thermal energy devices configured within the fluid distribution network.
- Rationale: Thermal energy generated by equipment operation may be recovered and redirected to thermal loads or converted to meet mechanical and electrical loads, thereby reducing demand for energy production.

### REQ-117: Shipboard Water Services (Container)

#### REQ-118: Freshwater Production (Functional)
Seawater taken in from the surrounding environment shall undergo desalination via reverse osmosis or distillation processes.
(Assumption: for simplification, freshwater services intakes seawater only)
- Rationale: Freshwater production onboard reduces dependence on shore-side and underway replenishment.

#### REQ-119: Freshwater Storage (Functional)
After production, freshwater shall flow through the distribution network to storage tanks.
The freshwater storage service shall retain freshwater in designated tanks while preserving the volume and water quality required for subsequent shipboard use.
- Rationale: Freshwater must be retained between production and consumption so that shipboard demand can be met despite variations in production rate, replenishment availability, and usage.
  (Assumption: freshwater is not distributed to consumption outlets immediately after production and moved to tanks first instead)

#### REQ-120: Machinery Makeup Water (Functional)
Freshwater shall be added to closed-loop machinery circuits based on monitored water levels and the volume of water lost.
- Rationale: Closed-loop machinery circuits, such as those carrying primary coolant, lose water to blowdown, evaporation, and leaks; to keep the circulated water volume within operating limits, the lost water must be replenished.

#### REQ-121: Potable Water Production (Functional)
Freshwater shall be remineralized, pH-adjusted, and disinfected so that the end product is potable.
(Assumption: for simplification, potable water services intakes freshwater only)
- Rationale: Personnel require potable water for drinking, food preparation, and hygiene.

### REQ-122: Waste Management (Container)

#### REQ-123: Bilge Water Disposal (Container)

##### REQ-124: Oily Bilge Water (Functional)
Oily bilge water shall be processed through the bilge water management system so that oil and water are separated and directed to onboard holding and overboard discharge, respectively.
- Rationale: Machinery operation generates oily bilge water that requires controlled handling to prevent marine pollution.

##### REQ-125: Hold Bilge (Functional)
If the bilge water passes verification as free of oil and chemical residues from the bilge well, the hold bilge shall be discharged overboard via the cargo hold pumping system.
- Rationale: Hold bilge generally contains only water, and thus may be pumped overboard instead of to an OWS collecting tank.

#### REQ-126: Sewage Disposal (Functional)
The sewage treatment plant (STP) shall process blackwater so that liquid and sludge are separated, treated with greywater for overboard pumping and broken down in an aeration chamber for onboard holding, respectively.
Blackwater shall be processed through the sewage treatment plant (STP) so that liquid and sludge are separated, treated with grey water for overboard pumping and broken down in an aeration chamber for onboard holding, respectively.
(Assumption: liquid separated from blackwater is combined with greywater for treatment)
- Rationale: Sewage requires controlled treatment and disposition to protect personnel health and the marine environment.

#### REQ-127: Greywater Disposal (Functional)
The wastewater treatment system shall process greywater through filtration, aeration, and irradiation before pumping it overboard.
- Rationale: Greywater requires controlled treatment and disposition to protect personnel health and the marine environment.

#### REQ-128: Garbage Disposal (Functional)
An integrated waste management system comprising incinerators, compactors, comminuters, and marine sanitation devices shall process solid garbage and direct it to onboard holding for later disposal ashore.
- Rationale: In most cases, solid garbage may not be disposed of at sea; an integrated waste management system allows the different garbage categories to be handled accordingly.

### REQ-129: Atmospheric Management (Functional)

#### REQ-130: Emissions Management (Functional)
- Rationale: Propulsion machinery, auxiliary machinery, incineration equipment, and other onboard processes generate atmospheric emissions that require control to reduce environmental impact and satisfy applicable emission regulations.
  Basis: MARPOL Annex VI

##### REQ-131: Pollutant Control (Functional)
A combination of post-combustion and in-engine devices shall mitigate the emission of SOx and NOx pollutants.

##### REQ-132: GHG Control (Functional)
A combination of pre- and post-combustion measures shall prevent the generation of and capture GHGs resulting from combustion.

#### REQ-133: HVAC (Container)

##### REQ-134: Machinery Space Ventilation (Functional)

##### REQ-135: Cargo Hold Ventilation (Functional)

### REQ-136: Habitability and Ergonomics (Functional)

#### REQ-137: Domestic Water Use (Functional)

#### REQ-138: Lighting (Functional)

#### REQ-139: Accomodation HVAC (Functional)
(air handling, AHU = Air Handling Unit)

## NEED-02: Safety and Survivability (Functional)
The vessel must protect personnel, mission systems, and the platform from hazards encountered during routine operations while maintaining the ability to withstand and recover from foreseeable emergency conditions and failures.
- Rationale: Personnel safety, mission accomplishment, and preservation of the vessel depend upon preventing hazards during normal operation and maintaining essential capabilities during failures and emergency conditions.

### REQ-201: Operational Hazard Control (Container)

#### REQ-202: Hazardous Materials Management (Informational)
All hazardous materials shall be contained in structural isolation from the point of generation or initial stowage until transfer for approved disposal or treatment.
All hazardous material produced onboard shall be structurally isolated at the source.
(NOTE: this requirement needs to be decomposed further to be functional and implementable)
- Rationale: Hazardous materials require dedicated containment throughout their onboard lifecycle to prevent personnel exposure, environmental contamination, damage to ship systems, and regulatory noncompliance.

#### REQ-203: Guarding and Shielding (Functional)
Physical barriers shall shield personnel from the energy transfer of moving machinery and energized sources.
- Rationale: Physical barriers reduce the likelihood of personnel injury by preventing inadvertent contact with parts or environments that cause harmful energy transfer.

#### REQ-204: Fault Response (Informational)
Integrated fault response systems comprising detection systems, alarm sequences, redundancy, and automated or manual reset recovery pathways shall maintain system availability.
(NOTE: this requirement needs to be decomposed further to be functional and implementable)
- Rationale: Detecting faults, limiting their propagation through isolation, and transitioning affected systems back to baseline operating states keep systems online.

### REQ-205: Fire Protection (Container)

#### REQ-206: Fire Zoning (Functional)
Fire zone boundaries shall be integrated into the main hull structure.
- Rationale: Fire zoning limits the spread of fire and smoke between vessel spaces, mitigating cascading damage, protecting personnel, preserving shipboard systems, and providing time for emergency response and evacuation.

#### REQ-207: Fire SCADA (Informational)
The fire SCADA system shall detect and monitor fires, provide alarm signaling in response to detection, and actuate containment and fire suppression responses.
The fire SCADA system shall detect and monitor fires, provide alarm signaling in response to detection, and actuate the automated and centralized containment and fire suppression responses.
(Actuation is automatic or human-operated??)
(NOTE: this requirement is not truly single; for signularity, this requirement would have to be decomposed)
- Rationale: Centralized communication of fire status and operation of fire suppression systems enables early detection, streamlined emergency response and casualty assessment, and coordinated firefighting actions.

#### REQ-208: Fire Extinguishment (Functional)
High-risk spaces shall be fitted with the fire extinguishment system appropriate for the fire hazards present and capable of suppressing the corresponding class(es) of fire.
- Rationale: Different spaces pose different fire hazards; thus, permanently installed fire extinguishment systems must be selected according to the fire hazards associated with each space.

### REQ-209: Flood Protection (Container)

#### REQ-210: Sealed Integrity (Functional)
Hull and compartment boundaries shall be environmentally sealed in accordance with the watertight or weathertight designation of the boundary.
- Rationale: Environmentally sealed boundaries isolate flooding and reduce progressive flooding.

#### REQ-211: Hydrostatic Equalization (Container)

##### REQ-212: Cross-Flooding (Functional)
Dedicated cross-flooding pathways shall permit passive hydrostatic equalization through gravity-driven transfer of floodwater between designated compartments.
- Rationale: Passive cross-flooding arrangements mitigate excessive heel and hydrostatic instability without requiring powered equipment or continuous operator intervention.

##### REQ-213: Counter-Flooding (Functional)
The ballast system shall permit active hydrostatic equalization through the manual alignment of valves into counter-flooding configurations.
- Rationale: Active counter-flooding arrangements correct excessive heel or trim by intentionally flooding intact compartments through the vessel's ballast distribution system.

#### REQ-214: Flooding SCADA (Functional)
The flooding SCADA system shall detect and monitor floods, provide alarm signaling in response to detection, and actuate the automated and centralized containment, equalization, and dewatering responses.
- Rationale: Centralized communication of flooding status and operation of flooding response systems enables early detection, streamlined emergency response and casualty assessment, and coordinated firefighting actions.

#### REQ-215: Emergency Dewatering (Functional)
Emergency dewatering architecture comprising drainage pathways that integrate mechanical suction, high-pressure hydraulic eductors, and isolated backup pumping shall pump floodwater overboard.
- Rationale: Dewatering discharges floodwater to restore stability, loading, and equipment operating conditions.

### REQ-216: Critical Function Continuity (Container)

#### REQ-217: Critical Function Independence (Functional)
Critical functions shall be architecturally independent such that the loss of a single compartment, service, or subsystem does not disable other functions through common dependencies.
Critical functions shall be architecturally independent such that common dependencies are minimized.
- Rationale: Architectural independence reduces common-cause failures by limiting the propagation of a single casualty across multiple critical vessel functions during damage-control scenarios.

#### REQ-218: Emergency Utilities (Functional)
Utilities that serve critical functions shall have source independence
The critical function utilities provided by platform support shall have offline or blackout redundancy integrated into, or independent of, the system from which they originate under standard operating conditions.

#### REQ-219: Degraded Operation (Functional)

### REQ-220: Evacuability (Container)

#### REQ-221: Survival Craft (Functional)

### REQ-222: Casualty Response (Container)

#### REQ-223: Casualty SCADA (Functional)

#### REQ-224: Essential Function Recovery (Functional)

## NEED-03: Seakeeping and Stability (Functional)
The vessel must remain stable and safe throughout the range of loading conditions and environmental conditions expected during its intended operations.
- Rationale: Vessel safety, operational capability, and the uncompromised transportation of cargo depend on maintaining acceptable equilibrium and motion response as weight distribution, fluid loading, mission configuration, and environmental conditions vary.

### REQ-301: Loading Condition (Functional)

#### REQ-302: Design Loading Conditions (Functional)
Still water moments, shear forces, and dynamic wave loading shall be evaluated for the fully loaded departure, fully loaded arrival, departure ballast, and arrival ballast conditions.
- Rationale: Defined loading states provide repeatable analysis cases of vessel loading and operation.

### REQ-303: Weight Distribution (Functional)
Each mass loaded onto the vessel shall be assigned a location based on the effect of its weight, as modeled along the vertical, longitudinal, and transverse axes of distribution, under lightship and deadweight conditions.
- Rationale: The longitudinal, transverse, and vertical distribution of vessel weight determines equilibrium attitude, center-of-gravity position, and righting characteristics.

#### REQ-304: Lightship Weight (Functional)

#### REQ-305: Variable Load (Functional)

#### REQ-306: Center of Gravity (Functional)

### REQ-307: Fluid Loading (Functional)
The allocation of fluid to tanks shall be informed by the effects of the distributed volumes as modeled for each design loading condition.
- Rationale: Tank contents affect displacement, trim, center of gravity, free-surface effects, and the vessel’s response to environmental excitation.

#### REQ-308: Free-Surface Effect (Functional)
The impact of partially filled tanks on the metacentric height of the vessel shall be determined using free-surface correction.
- Rationale: Fluid movement within a partially filled tank can reduce effective stability and alter dynamic response.

### REQ-309: Mission Systems Confirguration (Functional)
The arrangement of mission systems shall be approved based on the weight and center of gravity associated with each configuration
Mission-configuration properties shall specify the weight and center-of-gravity data associated with each approved mission-system configuration.
The configuration in which mission systems are installed shall be informed by how the arrangement affects vessel stability for each design loading condition.
- Rationale: Mass properties like weight and center of gravity determine vessel displacement, weight distribution, and motion characteristics.

### REQ-310: Loading Condition Coverage (Functional)
The limiting loading states shall be identified in the intended operating envelope.
- Rationale: Possible critical loading conditions must be defined in addition to the loaded conditions of routine operations.

## NEED-04: Endurance (Functional)
The vessel must sustain operations for the duration, range, and operational tempo required by its intended operational roles.
- Rationale: Mission accomplishment depends on the continued availability of propulsion, electrical power, mission systems, and essential ship services throughout the intended operating profile. Insufficient endurance may restrict operational range, reduce mission persistence, interrupt the required operating tempo, or require premature replenishment or mission termination. Endurance must therefore be evaluated against defined operating conditions, consumable-resource availability, expected resource demand, and required operational reserves.

### REQ-401: Fuel Storage Capacity (Functional)
The onboard fuel storage capacity shall be at least equal to the sum of the operational fuel quantity and reserve fuel quantity for each fuel type carried.
- Rationale: Onboard fuel storage establishes the fuel inventory available to fuel-consuming systems throughout vessel operations; the usable fuel inventory is determined by the intended operational profile and includes a contingency reserve.

#### REQ-402: Usable Fuel Inventory (Functional)
The usable inventory of each fuel type shall support at least 100 days of operation for all active consumers requiring that fuel type under the selected operating profile.
- Rationale: Continuous vessel operation depends on the availability of usable fuel onboard, and the duration of an operational period is one factor that determines the minimum fuel inventory.

#### REQ-403: Reserve Fuel Quantity (Functional)
The onboard usable fuel inventory shall include reserve fuel quantities that collectively allow vessel operation for at least 1% of the intended operational duration.
Assumption: The reserve operating duration is provisionally set to 1% of the intended operational period under the assumptions that this reserve is sufficient and that this approach to determining the reserve needed is appropriate. This value shall be updated if an applicable MSC requirement or case-study-specific directive is identified. This approach to determining the quantity of fuel to be reserved also implicitly assumes that the rate of consumption under contingencies is the same as that provided for in the standard operating profile.
- Rationale: The intended operational period may be extended or disrupted by delays, route deviations, adverse environmental conditions, equipment casualties, or other contingencies. A reserve operating duration equal to 1% of the intended operational duration provides limited continued vessel operation when actual fuel consumption exceeds the planned operational requirement.

#### REQ-404: Fuel Type Allocation (Functional)
For each onboard fuel type, the usable fuel quantity shall be greater than or equal to the operational fuel quantity plus a reserve equal to 1% of that operational fuel quantity.
Assumption: Fuel consumption rates and the relative distribution of demand among fuel types remain constant throughout the reserve operating period.
- Rationale: Allocating fuel inventory by fuel type ensures that each fuel-consuming system has sufficient operational and reserve fuel to sustain its required function throughout the intended operational and reserve operating periods.

### REQ-405: Fuel Delivery (Functional)
Each active fuel consumer shall receive its required fuel type.
- Rationale: Active consumers must receive their respective fuel types so they can convert chemical energy into the mechanical energy required for mechanical and electrical power generation.

#### REQ-406: Fuel Delivery Rate (Functional)
The aggregate rate of fuel delivery shall be greater than or equal to the aggregate rate of fuel demand of all active fuel consumers for the selected operating profile.
Assumption: This performance requirement assumes that comparing the aggregate rate of fuel delivery with the aggregate rate of fuel demand accurately represents the fuel delivery networks' ability to supply fuel at the rates needed for operation. This assumption does not represent cases in which the aggregate delivery rate meets the aggregate rate of demand because some rates of delivery are too high while others are too low with respect to fuel type, and these discrepancies cancel each other out when rates are summed.
NOTE: The current test_fuel.m script verifies only the aggregate fuel-rate balance. Full verification requires grouping fuel supply and demand by fuel type before performing the comparison.
- Rationale: The fuel-delivery rate must meet or exceed the combined fuel demand of all active consumers to prevent interruption of vessel operations.

#### REQ-407: Fuel Conditioning (Functional)
Fuel shall flow through the conditioning subsystem appropriate for its fuel type and exit with the physical properties within the specified limits at the inlet of its assigned downstream fuel consumer.
- Rationale: Fuel-consuming equipment depends on fuel entering at the temperature, pressure, and purification condition compatible with its combustion and fuel-handling requirements to prevent equipment degredation or interrupted fuel consumption.

#### REQ-408: Fuel Routing (Functional)
Fuel shall be routed from storage to its active consumers via the distribution network corresponding to its fuel type, conditioning needs, and delivery rates.
- Rationale: Routing makes fuel delivery possible by giving fuel the directionality and impetus necessary for it to flow from source to sink.

#### REQ-409: Consumer Fuel Supply (Functional)
At each interface between the fuel delivery network and an active fuel consumer, fuel shall be delivered in a compatible form with the receiving consumer's operating parameters.
At each piping-to-consumer interface, the fuel supply system shall deliver fuel at the set pressure and temperature within the specified inlet operating limits of the receiving fuel-consuming equipment.
- Rationale: For the consumer to accept and use the fuel supplied by the fuel delivery system, the fuel must have the physical properties that allow it to pass through the point of consumption without interruption.
  NOTE: We have not yet defined what the acceptable fuel delivery conditions are for the fuel to be used by the active consumer.

### REQ-410: Compressed Air Resource (Container)

#### REQ-411: Compressed Air Generation (Functional)
Air compressors shall store potential energy in air by drawing in and compressing ambient air.
- Rationale: Critical and essential machinery demand compressed air at rates that necessitate onboard generation to sustain their operation.

#### REQ-412: Compressed Air Storage (Functional)
After generation, compressed air shall flow through a pressure- and temperature-controlled pipeline network to air receivers for storage.
- Rationale: Compressed air must be stored after generation and before use because on-demand production would cause undue wear on the air compressor, compromise pressurization and flow consistency, and prevent delivery that meets the intensity and rate of demand imposed by critical consumers.

### REQ-413: Lube Oil Resource (Container)

#### REQ-414: Lube Oil Storage (Functional)

#### REQ-415: Lube Oil Conditioning (Functional)

### REQ-416: Hydraulic Fluid Resource (Container)

#### REQ-417: Hydraulic Fluid Storage (Functional)

#### REQ-418: Hydraulic Fluid Conditioning (Functional)

### REQ-419: Potable Water Resource (Container)

#### REQ-420: Potable Water Storage (Functional)
The potable storage service shall retain freshwater in designated tanks while preserving the volume and water quality required for subsequent shipboard use.
- Rationale: Potable water must be retained between production or replenishment and consumption so that shipboard demand can be met despite variations in production rate, replenishment availability, and usage.
  (Assumption: potable water is not distributed to consumption outlets immediately after production and moved to tanks first instead)

#### REQ-421: Potable Water Distribution (Functional)
The potable water distribution service shall use pumps and valves configured in designated paths to convey freshwater to and from storage tanks at flow rates and pressures in accordance with the defined parameters.
- Rationale: Potable water tanks and consumers require controlled conveyance to ensure storage safety, point-of-use safety, and practical use.

### REQ-422: Consumables (Functional)

#### REQ-423: Consumables Storage (Functional)

#### REQ-424: Provision Refrigeration (Functional)

## NEED-05: Mobility and Maneuverability (Functional)
The vessel must provide both precise and long-range control over vessel movement to facilitate strategic transit, port, bunkering, and mission operations within the intended operating environments.
- Rationale: Different phases of operation—including long-distance transit, harbor maneuvering, bunkering, and mission execution—place different demands on vessel mobility and maneuverability. Providing both precise low-speed control and efficient long-range mobility enables the vessel to accomplish its operational objectives safely and effectively.

### REQ-501: Longitudinal Motion Control (Functional)

#### REQ-502: Propulsive Force Generation (Functional)
The propulsion train shall generate thrust in the ahead and astern directions.
- Rationale: Propulsive force is required to overcome vessel resistance and produce controlled forward and backward motion.

#### REQ-503: Propulsive Force Regulation (Functional)
The propulsion train shall regulate longitudinal propulsive thrust to establish, maintain, and modify commanded longitudinal vessel speed.
- Rationale: Controlled regulation of longitudinal propulsive thrust is required to enable predictable acceleration, deceleration, and steady-state operation of the vessel.

#### REQ-504: Longitudinal Motion Arrest (Functional)
Systems, including the propulsion train and anchoring system, shall reduce longitudinal velocity to zero by generating a resistive force opposite to thrust.
Systems that provide longitudinal motion resistance (?)
- Rationale: Stopping capability is required to control the vessel's position in standard operating conditions and to prevent collision in emergency events.

##### REQ-505: Absolute Stopping (Functional)
Longitudinal velocity shall decelerate from [vi] to zero within [d] in [t].
Assumption: Conditions are assumed to be...

### REQ-506: Maneuvering (Functional)

#### REQ-507: Course Keeping (Functional)
The vessel shall regulate steering-induced yaw moment to counteract disturbing yaw moments and maintain a commanded course.
- Rationale: To execute maneuvering functions, maintain directional stability, and navigate accurately, steering must prevent unintended yaw acceleration such that the vessel maintains its commanded course despite environmental and operational disturbances.

##### REQ-508: Course Keeping Precision (Functional)
The vessel shall be aligned with its commanded course within ±[X] degrees at [v].
Assumption: (describe the environmental and loading conditions this performance requirement applies to)

#### REQ-509: Heading Change (Functional)
The steering system shall generate and regulate the yaw moment that achieves the commanded change in heading.
- Rationale: Maneuvers such as the execution of turns, change of course, and hazard avoidance necessitate the vessel's capability to change heading.

##### REQ-510: Turning Response (Functional)
The vessel shall complete a commanded heading change of [X] degrees within [Y] seconds without exceeding [Z] degrees of heading overshoot.
Assumption: (specify conditions)

##### REQ-511: Tactical Diameter (Functional)
The vessel shall maintain a tactical diameter less than or equal to [D] during a turning circle maneuver.
Assumption: (specify operating conditons)

##### REQ-512: Advance (Functional)
The vessel shall maintain an advance less than or equal to [A] during a turning circle maneuver.
Assumption: (specify conditions)

##### REQ-513: Transfer (Functional)
The vessel shall maintain a transfer less than or equal to [T] during a turning circle maneuver.
Assumption: (specify conditons)

#### REQ-514: Turn Arrest (Functional)
The steering system shall generate and regulate yaw moment to reduce vessel yaw rate to zero at the commanded heading.
- Rationale: The capability to arrest turning motion is required to prevent overshoot and establish the commanded vessel heading following a heading-change maneuver.

## NEED-06: Mission Systems Support (Functional)
The vessel must deploy the mission-specific systems necessary to perform mission operations.
(Assumption: disregard lifecycle considerations for simplicity)
- Rationale: Mission accomplishment depends on the operability of mission systems.

### REQ-601: Mission Systems Integration (Functional)
Mission systems integration shall unite mission systems with the platform through interfaces and standardized physical connections.
- Rationale: The operability of mission systems depends on their connectivity with the platform, such that the exchange of physical resources and information necessary for mission operations may occur.

### REQ-602: Mission Systems Operation (Functional)
Control systems shall execute commands issued by designated human and automated operators.
- Rationale: For the equipment associated with the mission system to serve its intended purposes, operators must be able to command equipment behavior.

### REQ-603: Mission Information (Functional)
Cyber-physical systems shall generate and report mission information by running information processing cycles.
- Rationale: Information allows an operator to be certain that the command they issue instructs appropriate control.

### REQ-604: Mission Communications (Functional)
Authorized entities shall exchange mission information on the basis of interface-specific network protocols.
- Rationale: Mission-system operation depends upon the timely exchange of mission information between participating entities.

### REQ-605: Mission Resources (Functional)
Physical gradients and system requests shall route vessel resources through mission-systems-to-platform interfaces.
- Rationale: Mission systems require platform resources to perform their intended operational functions.
